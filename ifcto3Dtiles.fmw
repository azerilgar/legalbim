FME workspace ifcto3Dtiles.fmw

Parameters:
- DestDataset_CESIUM3DTILES = /Users/azerilgar/Workingdoc/BIMLegalSpace/tilesets   # Destination Cesium 3D Tiles Folder
- SourceDataset_DGNV8 = /Users/azerilgar/Documents/data/dgn-dwg/parcel3.DGN   # Source Bentley MicroStation Design File(s)
- SourceDataset_TEXTLINE = /Users/azerilgar/Documents/data/ifc/PRPJE101.txt   # Source Text File(s)
- SourceDataset_IFC_5 = /Users/azerilgar/Documents/data/ifc/PRPJE101.ifc   # Source Industry Foundation Class (IFC) File(s)
- FEATURE_TYPES_3 = IfcBeam IfcBeamType IfcBuildingElementProxy IfcBuildingElementProxyType IfcBuildingStorey IfcColumn IfcColumnType IfcDoor IfcDoorType IfcGrid IfcMember IfcMemberType IfcOpeningElement IfcProject IfcPropertySet IfcQuantitySet IfcRailing IfcRailingType IfcRamp IfcRampFlight IfcRampType IfcRoof IfcRoofType IfcSite IfcSlab IfcSlabType IfcSpace IfcSpaceType IfcStair IfcStairFlight IfcStairFlightType IfcStairType IfcWall IfcWallType IfcWindow IfcWindowType PropertySetDefinition QuantitySetDefinition

Readers:
- DGNV8_1: DGNV8 from $(SourceDataset_DGNV8) in EPSG:2321
- TEXTLINE_1: TEXTLINE from $(SourceDataset_TEXTLINE)
- IFC_3: IFC from $(SourceDataset_IFC_5) in EPSG:2321

Writers:
- CESIUM3DTILES_1: CESIUM3DTILES to $(DestDataset_CESIUM3DTILES)

IfcBeam (reader IFC_3)
    attributes: GlobalId char(22), Name string, Description string, ObjectType string, Tag varchar(255), PredefinedType enumeration, Annotation geometry, Axis geometry, Body geometry, Box geometry, FootPrint geometry, ApplicableOccurrence string, BuildingAddress.AddressLines string, BuildingAddress.Country varchar(255), BuildingAddress.Description string, BuildingAddress.InternalLocation varchar(255), BuildingAddress.PostalBox varchar(255), BuildingAddress.PostalCode varchar(255), BuildingAddress.Purpose enumeration, BuildingAddress.Region varchar(255), BuildingAddress.Town varchar(255), BuildingAddress.UserDefinedPurpose varchar(255), CompositionType string, ElementType varchar(255), Elevation real, ElevationOfRefHeight real, ElevationOfTerrain real, ElevationWithFlooring real, LandTitleNumber string, LongName string,
      NumberOfRisers int, NumberOfTreads int, OperationType enumeration, OverallHeight real, OverallWidth real, ParameterTakesPrecedence bool, PartitioningType enumeration, Phase string, RefElevation real, RefLatitude real, RefLongitude real, RiserHeight real, SiteAddress.AddressLines string, SiteAddress.Country varchar(255), SiteAddress.Description string, SiteAddress.InternalLocation varchar(255), SiteAddress.PostalBox varchar(255), SiteAddress.PostalCode varchar(255), SiteAddress.Purpose enumeration, SiteAddress.Region varchar(255), SiteAddress.Town varchar(255), SiteAddress.UserDefinedPurpose varchar(255), TreadLength real, UserDefinedOperationType varchar(255), UserDefinedPartitioningType varchar(255), ifc_property_set{} string, ifc_quantity_set{} string, ifc_type_object_id string
    -> FeatureTypeFilter_3
AttributeExposer
    ATTR_TABLE = Area,,CrossSectionArea,,GrossArea,,GrossFloorArea,,GrossFootprintArea,,GrossVolume,,Height,,NetVolume,,ifc_quantity_set_name,,NetFloorArea,
    -> AttributeFilter_9
AttributeFilter_9
    ATTR_NAME = ifc_quantity_set_name
    ATTR_VALUES = <Empty>,<Missing>,<Null>,<Unfiltered>,Qto_BeamBaseQuantities,Qto_ColumnBaseQuantities,Qto_WallBaseQuantities,Qto_SpaceBaseQuantities,Qto_SlabBaseQuantities
    Qto_WallBaseQuantities -> AttributeRenamer_3
    Qto_SpaceBaseQuantities -> FeatureMerger_13 [SUPPLIER]
AttributeRenamer_3
    ATTR_TABLE:
      RENAME_SET_DEFAULT NetVolume > NetVolumeWall
      RENAME_SET_DEFAULT GrossFloorArea > GrossFloorAreaWall
      RENAME_SET_DEFAULT NetFloorArea > NetFloorAreaWall
      RENAME_SET_DEFAULT GrossVolume > GrossVolumeWall
      RENAME_SET_DEFAULT Height > HeightWall
    KEEP_RENAMED_ONLY = no
    MISSING_INPUT_ATTRS = REMOVE
    -> FeatureMerger_14 [SUPPLIER]
AttributeExposer_9
    ATTR_LIST = IsExternal,LoadBearing,Width,Function,Number,Zone,"Space Type",Level,"Upper Limit",Area,Volume,Length,ifc_property_set_name
    -> AttributeFilter_6
AttributeFilter_6
    ATTR_NAME = ifc_property_set_name
    ATTR_VALUES = <Empty>,<Missing>,<Null>,<Unfiltered>,Pset_WallCommon,Pset_SpaceCommon,Wall Schedule,Space Schedule,Room Schedule
    Pset_WallCommon -> FeatureMerger_8 [SUPPLIER]
    Space Schedule -> FeatureMerger [SUPPLIER]
AttributeExposer_6
    ATTR_TABLE = ifc_quantities{0}.name,,ifc_quantities{0}.type,,ifc_quantities{1}.name,,ifc_quantities{1}.type,
AttributeExposer_7
    ATTR_TABLE = Elevation,,FootPrint,,ifc_quantity_set{0},
    -> AttributeFilter_2
FeatureMerger_13
    ATTR_ACCUM_MODE = Merge Supplier
    ATTR_CONFLICT_RES = Use Requestor
    IGNORE_NULLS = No
    JOIN_KEYS = @Value(ifc_quantity_set{0}) @Value(ifc_unique_id) AUTO
    MERGE_TYPE = Attributes Only
    PROCESS_DUPS = NO
    REJECT_NULL_MISSING_KEYS = No
    SUPPLIERS_FIRST = No
    MERGED -> FeatureMerger [REQUESTOR]
Reprojector_5
    DEST = LL-WGS84
    INTERPOLATION_TYPE_NAME = Nearest Neighbor
    RASTER_CELL_SIZE = Preserve Cells
    RASTER_TOLERANCE = 0.0
    SOURCE = EPSG:2321
    REPROJECTED -> Junction_3
GeometryPartExtractor_5
    GQUERY:
      for $geom in //geometry
      where $geom/@fme_geometry_type = ('IFMEBox', 'IFMEBRepSolid', 'IFMEExtrusion', 'IFMEMultiSolid', 'IFMECompositeSolid', 'IFMECSGSolid')
      return number($geom/@fme_id)
    EXTRACTED -> AttributeCopier
AttributeCopier
    ATTR_TABLE = COPY ifc_parent_id > GlobalId_IfcWall
    -> FeatureMerger_4 [REQUESTOR]
GeometryFilter_10
    FILTER_MODE = SIMPLE
    FILTER_MULTI = FILTER_TYPES]"Null Point Text Line Area Surface Solid Raster PointCloud VoxelGrid"]FME_CONTROLLER_QUERY_FILE]]FME_CONTROLLER_CHOICE]Simple
    Solid -> VolumeCalculator
AttributeValueMapper_4
    DIRECTION = Forward (Source To Destination)
    LUT = M_Rectangular Column:500 x 250mm,500 x 250,M_Rectangular Column:550 x 250mm 2,550 x 250
    SRC = ObjectType
    VAL_ATTR = columnSize
    -> Reprojector_8
Reprojector_8
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator
Reprojector_4
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator
Reprojector_2
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator_10
    REPROJECTED -> Aggregator
Aggregator_10
    ACCUM_ATTRS_NAME = Use Attributes From One Feature
    AGGREGATE_TYPE = Homogeneous Collection (If Possible)
    MODE = Geometry - Assemble One Level
    SEP = ,
    AGGREGATE -> Junction_4
AttributeExposer_5
    ATTR_LIST = ifc_instance_name,ifc_property_set{2},ifc_quantity_set{0}
    -> AttributeManager_19
AttributeManager_19
    ATTR_TABLE:
      SET_TO GlobalId_IfcWall = @Value(GlobalId)
      SET_TO ifc_parent_id_IfcWall = @Value(ifc_parent_id)
      RENAME_SET_VALUE ifc_property_set{2} > Pset_WallCommon_UniqueID
    -> AttributeCreator_6
AttributeCreator_6
    ATTR_TABLE:
      SET_TO GlobalId_IfcWall = @Value(GlobalId)
      SET_TO ifc_parent_id_IfcWall = @Value(ifc_parent_id)
    -> FeatureMerger_10 [SUPPLIER]
    -> FeatureMerger_14 [REQUESTOR]
FeatureMerger_14
    ATTR_ACCUM_MODE = Merge Supplier
    ATTR_CONFLICT_RES = Use Requestor
    IGNORE_NULLS = No
    JOIN_KEYS = @Value(ifc_quantity_set{0}) @Value(ifc_unique_id) AUTO
    MERGE_TYPE = Attributes Only
    PROCESS_DUPS = NO
    REJECT_NULL_MISSING_KEYS = No
    SUPPLIERS_FIRST = No
    MERGED -> FeatureMerger_8 [REQUESTOR]
FeatureMerger_8
    ATTR_ACCUM_MODE = Merge Supplier
    ATTR_CONFLICT_RES = Use Requestor
    IGNORE_NULLS = No
    JOIN_KEYS = @Value(Pset_WallCommon_UniqueID) @Value(ifc_unique_id) AUTO
    MERGE_TYPE = Attributes Only
    PROCESS_DUPS = NO
    REJECT_NULL_MISSING_KEYS = No
    SUPPLIERS_FIRST = No
    MERGED -> SurfaceFootprintReplacer
    MERGED -> FeatureMerger_15 [REQUESTOR]
    MERGED -> AreaCalculator_2
AttributeFilter_5
    ATTR_NAME = IsExternal
    ATTR_VALUES = <Empty>,<Missing>,<Null>,No,<Unfiltered>,Yes
    No -> AttributeFilter_7
    Yes -> AttributeManager
AttributeValueMapper_5
    DEFAULT_VALUE = -
    DIRECTION = Forward (Source To Destination)
    LUT = 3Kv40YSfLFseVd_Y9RwXhc,Basement Level,3Kv40YSfLFseVd_Y9RwJu1,Ground Level,3Kv40YSfLFseVd_Y9RwJCd,First Level,3Kv40YSfLFseVd_Y9RwXNT,Second Level,3Kv40YSfLFseVd_Y9RwXII,Attic Level
    SRC = ifc_parent_id
    VAL_ATTR = levelName
    -> Reprojector_10
Reprojector_10
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator
GeometryCoercer_2
    GQUERY:
      for $geom in //geometry
      where $geom/count(parent::geometry) = 0
      return number($geom/@fme_id)
    KIND = fme_brep_solid
    COERCED -> AttributeManager_18
AppearanceRemover_3
    SIDE_TO_REMOVE = Front and Back Sides
    -> Reprojector_12
Reprojector_12
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator
Reprojector_13
    DEST = LL-WGS84
    INTERPOLATION_TYPE_NAME = Nearest Neighbor
    RASTER_CELL_SIZE = Preserve Cells
    RASTER_TOLERANCE = 0.0
    SOURCE = EPSG:2321
    REPROJECTED -> Junction_4
Reprojector_3
    DEST = LL-WGS84
    INTERPOLATION_TYPE_NAME = Nearest Neighbor
    RASTER_CELL_SIZE = Preserve Cells
    RASTER_TOLERANCE = 0.0
    SOURCE = EPSG:2321
    REPROJECTED -> Junction_4
Reprojector_11
    DEST = LL-WGS84
    INTERPOLATION_TYPE_NAME = Nearest Neighbor
    RASTER_CELL_SIZE = Preserve Cells
    RASTER_TOLERANCE = 0.0
    SOURCE = EPSG:2321
    REPROJECTED -> Junction_4
text_line (reader TEXTLINE_1)
    attributes: text_line_data buffer
    -> TestFilter_3
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(text_line_data) CONTAINS IFCRELSPACEBOUNDARY",@Value(text_line_data) CONTAINS IFCRELSPACEBOUNDARY,"BOOL_OP,OR,COMPOSITE_TEST,""""""1"""""",TEST_CLAUSE,CASE_INSENSITIVE_TEST @Value(text_line_data) CONTAINS IFCZONE",@Value(text_line_data) CONTAINS IFCZONE
    @Value(text_line_data) CONTAINS IFCRELSPACEBOUNDARY -> AttributeSplitter_2
AttributeSplitter_2
    ATTR_NAME = text_line_data
    DELIMITER = =
    DROP_EMPTY_PARTS = NO
    LIST_NAME = _list
    TRIM_TYPE = BOTH
    -> AttributeRenamer_2
AttributeRenamer_2
    ATTR_TABLE:
      RENAME_SET_DEFAULT _list{0} > RelSpaceBoundaryID
      RENAME_SET_DEFAULT _list{1} > temp
    KEEP_RENAMED_ONLY = no
    MISSING_INPUT_ATTRS = REMOVE
    -> AttributeSplitter
AttributeSplitter
    ATTR_NAME = temp
    DELIMITER = ,
    DROP_EMPTY_PARTS = NO
    LIST_NAME = _list
    TRIM_TYPE = BOTH
    -> AttributeManager_23
AttributeManager_23
    ATTR_TABLE:
      SET_TO (varchar(200))
      RENAME_SET_VALUE _list{0} > RelSpaceBoundaryGUID (varchar(200)) = @Right(@Trim(@Value(RelSpaceBoundaryGUID),IFCRELSPACEBOUNDARY'),@sub(@StringLength(@Trim(@Value(RelSpaceBoundaryGUID),IFCRELSPACEBOUNDARY')),2))
      RENAME_SET_VALUE _list{1} > OwnerHistory (varchar(200))
      RENAME_SET_VALUE _list{2} > Level (varchar(200))
      REMOVE _list{3} (varchar(200))
      RENAME_SET_VALUE _list{4} > RelatingSpace (varchar(200)) = @TrimLeft(@Value(RelatingSpace),#)
      RENAME_SET_VALUE _list{5} > RelatedBuildingElement (varchar(200)) = @TrimLeft(@Value(RelatedBuildingElement),#)
      RENAME_SET_VALUE _list{6} > ConnectionGeometry (varchar(200)) = @TrimLeft(@Value(ConnectionGeometry),#)
      RENAME_SET_VALUE _list{7} > PhysicalOrVirtual (varchar(200)) = @Trim(@Value(PhysicalOrVirtual),.)
      RENAME_SET_VALUE _list{8} > InternalOrExternal (varchar(200)) = @Left(@Trim(@Value(InternalOrExternal),.),8)
      REMOVE _list{9} (varchar(200))
      REMOVE _list{10} (varchar(200))
      SET_TO RelSpaceBoundaryID (varchar(200)) = @TrimLeft(@Value(RelSpaceBoundaryID),#)
    -> FeatureMerger_3 [REQUESTOR]
Junction_5
    -> GeometryFilter_5
GeometryFilter_5
    FILTER_MODE = SIMPLE
    FILTER_MULTI = FILTER_TYPES]"Null Point Text Line Area Surface Solid Raster PointCloud VoxelGrid"]FME_CONTROLLER_QUERY_FILE]]FME_CONTROLLER_CHOICE]Simple
    Solid -> AttributeManager_25
AttributeManager_25
    ATTR_TABLE:
      SET_TO Volume = @round(@Value(Volume),2)
      SET_TO Length = @round(@Value(Length),2)
      SET_TO wallAreaFootprint = @round(@Value(wallAreaFootprint),2)
      SET_TO Area = @Value(wallAreaFootprint)
    -> Reprojector_6
    -> FeatureMerger_4 [SUPPLIER]
Reprojector_6
    DEST = LL-WGS84
    INTERPOLATION_TYPE_NAME = Nearest Neighbor
    RASTER_CELL_SIZE = Preserve Cells
    RASTER_TOLERANCE = 0.0
    SOURCE = EPSG:2321
    REPROJECTED -> Junction_3
    REPROJECTED -> Aggregator
Aggregator
    ACCUM_ATTRS_NAME = Drop Incoming Attributes
    AGGREGATE_TYPE = Homogeneous Collection (If Possible)
    MODE = Geometry - Assemble One Level
    SEP = ,
    AGGREGATE -> Aggregator_9
Aggregator_9
    ACCUM_ATTRS_NAME = Merge Incoming Attributes
    AGGREGATE_TYPE = Homogeneous Collection (If Possible)
    MODE = Geometry - Assemble One Level
    SEP = ,
    AGGREGATE -> AttributeManager_21
AttributeManager_21
    ATTR_TABLE:
      SET_TO cesEntityType (varchar(11)) = IfcBuilding
      SET_TO cesPhysicalProperty (varchar(8)) = Building
    -> AppearanceRemover_4
AppearanceRemover_4
    SIDE_TO_REMOVE = Front and Back Sides
    -> CoordinateSystemSetter
CoordinateSystemSetter
    COORDSYS = LL-WGS84
    -> Junction_3
Junction_3
    -> tileset00 (writer CESIUM3DTILES_1)
tileset00 (writer CESIUM3DTILES_1)
    attributes: cesEntityType string, cesLegalSpaceType string, cesLegalSpaceSubtype string, cesPhysicalProperty string, GlobalId string, Name string, Description string, ObjectType string, LongName string, CompositionType string, Axis string, Body string, Box string, FootPrint string, ifc_parent_id string, ifc_parent_unique_id string, ifc_property_set{} string, ifc_quantity_set{} string, ifc_type_object_id string, ifc_unique_id string, _hierarchy_child_id_list{} string, _hierarchy_id string, _hierarchy_parent_id string, ifc_property_set_name string, Number string, Level string, Zone string, ifc_instance_name string, Space Type string, ElevationOfRefHeight float,
      ElevationOfTerrain float, BuildingAddress.Purpose string, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, IsExternal string, LoadBearing string, Width string, Function string, Upper Limit string, Area string, Volume string, Length string, levelName string, elevationRelative string, PredefinedType string, ElevationWithFlooring float, Tag string, Pset_WallCommon.ExtendToStructure string, Pset_WallCommon.IsExternal string, Pset_WallCommon.LoadBearing string, Pset_WallCommon.Reference string, OwnerHistory string, RelatingSpace string,
      RelatedBuildingElement string, ConnectionGeometry string, PhysicalOrVirtualBoundary string, InternalOrExternalBoundary string, wall_ifc_instance_name string, GlobalId_IfcWall string, ifc_parent_id_IfcWall string, OverallHeight float, OverallWidth float, PartitioningType string, UserDefinedPartitioningType string, NumberOfRisers int, NumberOfTreads int, RiserHeight float, TreadLength float, OperationType string, UserDefinedOperationType string, Annotation string, ApplicableOccurrence string, ElementType string, Elevation string, LandTitleNumber string, ParameterTakesPrecedence boolean, Phase string, RefElevation float, RefLatitude float, RefLongitude float, SiteAddress.AddressLines string, SiteAddress.Country string, SiteAddress.Description string,
      SiteAddress.InternalLocation string, SiteAddress.PostalBox string, SiteAddress.PostalCode string, SiteAddress.Purpose string, SiteAddress.Region string, SiteAddress.Town string, SiteAddress.UserDefinedPurpose string, Sorter string, ifc_quantity_set{0} string, CrossSectionArea string, GrossArea string, GrossFloorAreaSpace string, GrossFootprintAreaSpace string, GrossVolume string, HeightSpace string, NetVolumeSpace string, ifc_quantity_set_name string, NetFloorAreaSpace string, AreaSpaceSch string, _is_void string, _geometry_name string, _part_number string, _xmax float, _xmin float, _ymax float, _ymin float, _zmax float, _zmin float, topElevation string, area string,
      numReferences string, wallAreaFootprint float, _volume string, Pset_WallCommon_UniqueID string, NetVolumeWall string, GrossFloorAreaWall string, NetFloorAreaWall string, GrossVolumeWall string, HeightWall string, GrossFootprintArea string, text_line_data string, _list{} string, RelSpaceBoundaryGUID string, PhysicalOrVirtual string, InternalOrExternal string, RelSpaceBoundaryID string, temp string, GrossFloorArea string, Height string, NetVolume string, NetFloorArea string, columnSize string, storey_id string
FeatureMerger_4
    ATTR_ACCUM_MODE = Merge Supplier
    ATTR_CONFLICT_RES = Use Requestor
    IGNORE_NULLS = No
    JOIN_KEYS = @Value(GlobalId_IfcWall) @Value(GlobalId_IfcWall) AUTO
    MERGE_TYPE = Attributes Only
    PROCESS_DUPS = NO
    REJECT_NULL_MISSING_KEYS = No
    SUPPLIERS_FIRST = No
    MERGED -> AppearanceMerger [REQUESTOR]
    USED_SUPPLIER -> AppearanceMerger [SUPPLIER]
    USED_SUPPLIER -> Aggregator_4
    UNUSED_SUPPLIER -> AttributeFilter
AppearanceMerger
    R_GQUERY:
      for $geom in //geometry
      where $geom/count(parent::geometry) = 0
      return number($geom/@fme_id)
    R_SET_ON_SIDE = Front and Back Sides
    S_GET_FROM_SIDE = Front Side
    S_GQUERY:
      for $geom in //geometry
      where $geom/count(parent::geometry) = 0
      return number($geom/@fme_id)
    TEXTURE_MAPPING_TYPE_CHOICE = From Top View
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator_4
AttributeManager_9 [off]
    ATTR_TABLE:
      REMOVE Name
      REMOVE Description
      REMOVE ObjectType
      REMOVE LongName
      REMOVE CompositionType
      REMOVE PredefinedType
      REMOVE ElevationWithFlooring
      REMOVE Axis
      REMOVE Body
      REMOVE Box
      REMOVE FootPrint
      REMOVE Tag
      SET_TO fme_feature_type = IfcWall
      REMOVE Pset_WallCommon.ExtendToStructure
      REMOVE Pset_WallCommon.IsExternal
      REMOVE Pset_WallCommon.LoadBearing
      REMOVE Pset_WallCommon.Reference
      REMOVE _hierarchy_child_id_list{}
      REMOVE _hierarchy_id
      REMOVE _hierarchy_parent_id
      REMOVE OwnerHistory
      REMOVE RelatingSpace
      REMOVE RelatedBuildingElement
      REMOVE ConnectionGeometry
      REMOVE PhysicalOrVirtualBoundary
      REMOVE InternalOrExternalBoundary
      REMOVE wall_ifc_instance_name
      REMOVE ifc_property_set_name
      REMOVE Number
      REMOVE Level
      REMOVE Zone
      REMOVE OverallHeight
      REMOVE OverallWidth
      REMOVE OperationType
      REMOVE UserDefinedOperationType
      REMOVE NumberOfRisers
      REMOVE NumberOfTreads
      REMOVE RiserHeight
      REMOVE TreadLength
      REMOVE PartitioningType
      REMOVE UserDefinedPartitioningType
      REMOVE Space Type
      REMOVE ElevationOfRefHeight
      REMOVE ElevationOfTerrain
      REMOVE BuildingAddress.Purpose
      REMOVE BuildingAddress.Description
      REMOVE BuildingAddress.UserDefinedPurpose
      REMOVE BuildingAddress.InternalLocation
      REMOVE BuildingAddress.AddressLines
      REMOVE BuildingAddress.PostalBox
      REMOVE BuildingAddress.Town
      REMOVE BuildingAddress.Region
      REMOVE BuildingAddress.PostalCode
      REMOVE BuildingAddress.Country
      REMOVE Width
      REMOVE Function
      REMOVE Upper Limit
      SET_TO Volume = @round(@Value(Volume),2)
      SET_TO Length = @round(@Value(Length),2)
      SET_TO wallAreaFootprint = @round(@Value(wallAreaFootprint),2)
      SET_TO Area = @Value(wallAreaFootprint)
      REMOVE Pset_WallCommon_UniqueID
      REMOVE Annotation
      REMOVE text_line_data
      REMOVE _list{}
      REMOVE RelSpaceBoundaryGUID
      REMOVE PhysicalOrVirtual
      REMOVE InternalOrExternal
      REMOVE RelSpaceBoundaryID
      REMOVE temp
FeatureJoiner [off]
    ATTR_CONFLICT_RES = Prefer Left
    GEOMETRY_HANDLING = Prefer Left
    GROUP_BY = GlobalId_IfcWall
    JOIN_KEYS = GlobalId_IfcWall GlobalId_IfcWall AUTO
    JOIN_MODE = Left
    JOINED -> Aggregator_12
Aggregator_12 [off]
    ACCUM_ATTRS_NAME = Merge Incoming Attributes
    AGGREGATE_TYPE = Heterogeneous Collection
    GROUP_BY = GlobalId_IfcWall
    MODE = Geometry - Assemble One Level
    SEP = ,
    AGGREGATE -> DuplicateFilter_3
AppearanceRemover
    SIDE_TO_REMOVE = Front and Back Sides
    -> footprintAra_2 [SurfaceFootprintReplacer_2_Input]
Reprojector_7
    DEST = LL-WGS84
    INTERPOLATION_TYPE_NAME = Nearest Neighbor
    RASTER_CELL_SIZE = Preserve Cells
    RASTER_TOLERANCE = 0.0
    SOURCE = EPSG:2321
    REPROJECTED -> Junction_4
AttributeRounder_2
    PLACES = 2
    ROUND_TYPE = Nearest
    SRC_ATTRS = Area Volume WallGrossVolume WallNetVolume footprintArea_CAL wallAreaFootprint
    -> GeometryFilter_2
GeometryFilter_2
    FILTER_MODE = SIMPLE
    FILTER_MULTI = FILTER_TYPES]"Null Point Text Line Area Surface Solid Raster PointCloud VoxelGrid"]FME_CONTROLLER_QUERY_FILE]]FME_CONTROLLER_CHOICE]Simple
    Solid -> Reprojector_9
Reprojector_9
    DEST = LL-WGS84
    INTERPOLATION_TYPE_NAME = Nearest Neighbor
    RASTER_CELL_SIZE = Preserve Cells
    RASTER_TOLERANCE = 0.0
    SOURCE = EPSG:2321
    REPROJECTED -> Junction_4
Junction_4
    -> tilesetLegal (writer CESIUM3DTILES_1)
tilesetLegal (writer CESIUM3DTILES_1)
    attributes: cesEntityType string, cesLegalSpaceType string, cesLegalSpaceSubtype string, cesPhysicalProperty string, propertyID string, parcelNumber string, lotNumber string, sheetNumber string, district string, city string, area string, useType string, Zone string, wallAreaFootprint float, Area string, _volume string, Volume string, CrossSectionArea string, GrossArea string, GrossFloorArea string, GrossFootprintArea string, GrossVolume string, NetVolume string, GlobalId_IfcWall string, GlobalId string, Name string, Description string, ObjectType string, LongName string, CompositionType string,
      PredefinedType string, ElevationWithFlooring float, Axis string, Body string, Box string, FootPrint string, ifc_parent_id string, ifc_parent_unique_id string, ifc_property_set{} string, ifc_quantity_set{} string, ifc_type_object_id string, ifc_unique_id string, Tag string, Pset_WallCommon.ExtendToStructure string, Pset_WallCommon.IsExternal string, Pset_WallCommon.LoadBearing string, Pset_WallCommon.Reference string, _hierarchy_child_id_list{} string, _hierarchy_id string, _hierarchy_parent_id string, OwnerHistory string, RelatingSpace string, RelatedBuildingElement string, ConnectionGeometry string, PhysicalOrVirtualBoundary string, InternalOrExternalBoundary string, wall_ifc_instance_name string, ifc_property_set_name string, Number string, Level string,
      ifc_instance_name string, ifc_parent_id_IfcWall string, OverallHeight float, OverallWidth float, OperationType string, UserDefinedOperationType string, NumberOfRisers int, NumberOfTreads int, RiserHeight float, TreadLength float, PartitioningType string, UserDefinedPartitioningType string, Space Type string, numReferences string, ElevationOfRefHeight string, ElevationOfTerrain string, BuildingAddress.Purpose string, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, IsExternal string, LoadBearing string, Width string, Function string,
      Upper Limit string, Length string, levelName string, elevationRelative string, Pset_WallCommon_UniqueID string, Annotation string, ifc_quantity_set{0} string, ApplicableOccurrence string, ElementType string, Elevation float, LandTitleNumber string, ParameterTakesPrecedence boolean, Phase string, RefElevation float, RefLatitude float, RefLongitude float, SiteAddress.AddressLines string, SiteAddress.Country string, SiteAddress.Description string, SiteAddress.InternalLocation string, SiteAddress.PostalBox string, SiteAddress.PostalCode string, SiteAddress.Purpose string, SiteAddress.Region string, SiteAddress.Town string, SiteAddress.UserDefinedPurpose string, WallGrossVolume string, Height string, WallNetVolume string, ifc_quantity_set_name string,
      text_line_data string, _list{} string, RelSpaceBoundaryGUID string, PhysicalOrVirtual string, InternalOrExternal string, RelSpaceBoundaryID string, temp string, NetVolumeWall string, GrossFloorAreaWall string, NetFloorAreaWall string, GrossVolumeWall string, HeightWall string, AreaSpaceSch string, NetFloorArea string, Sorter string, GrossFloorAreaSpace string, GrossFootprintAreaSpace string, HeightSpace string, NetVolumeSpace string, NetFloorAreaSpace string, footprintArea_CAL float, VolumeSpace float, share string, _is_void string, _geometry_name string, _part_number string, _xmax float, _xmin float, _ymax float, _ymin float,
      _zmax float, _zmin float, topElevation string
AppearanceExtractor
    ACCUM_ATTRS = No
    ACCUM_TRAITS = No
    SIDE_TO_EXTRACT = Front and Back Sides
    UNIQUE_STYLES = Yes
    APPEARANCE -> AttributeFilter_8
AttributeFilter_8
    ATTR_NAME = fme_appearance_style_name
    ATTR_VALUES = <Empty>,<Missing>,<Null>,<Unfiltered>,Default Wall
AppearanceStyler
    ALPHA = 1.0
    AMBIENT_COLOR = 1,0.337255,0.282353
    APPEARANCE_NAME = ff
    DIFFUSE_COLOR = 1,1,1
    EMISSIVE_COLOR = 1,0.792157,0.294118
    SPECULAR_COLOR = 0.819608,1,0.588235
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
AppearanceSetter
    ALPHA = 0.5
    AMBIENT_COLOR = 0.545098,0.698039,1
    APPEARANCE_NAME = space
    DEF_STORAGE = Replace Existing Definitions
    DIFFUSE_COLOR = 0.65098,1,0.968627
    EMISSIVE_COLOR = 0.87451,1,0.780392
    GQUERY:
      for $geom in //geometry
      where $geom/count(parent::geometry) = 0
      return number($geom/@fme_id)
    SET_ON_SIDE = Front and Back Sides
    SHININESS = 0
    SPECULAR_COLOR = 1,0.878431,0.654902
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No

Bookmark: New Bookmark
FeatureTypeFilter_3
    ATTRIBUTES = IfcPropertySet,<Blank>,<Unfiltered>,QuantitySetDefinition,IfcQuantitySet
    IfcPropertySet -> AttributeExposer_9
    <UNFILTERED> -> AttributeExposer_8
    QuantitySetDefinition -> AttributeExposer_6
    IfcQuantitySet -> AttributeExposer
AttributeExposer_8
    ATTR_LIST = fme_feature_type,ifc_instance_name,PredefinedType
    -> AttributeCreator_5
AttributeCreator_5
    ATTR_TABLE:
      SET_TO cesEntityType = @Value(fme_feature_type)
      SET_TO cesLegalSpaceType
      SET_TO cesLegalSpaceSubtype
      SET_TO cesPhysicalProperty
      SET_TO levelName
      SET_TO elevationRelative
    -> AttributeValueMapper
AttributeValueMapper
    DEFAULT_VALUE = -
    DIRECTION = Forward (Source To Destination)
    LUT = 3Kv40YSfLFseVd_Y9RwXhc,Basement Level,3Kv40YSfLFseVd_Y9RwJu1,Ground Level,3Kv40YSfLFseVd_Y9RwJCd,First Level,3Kv40YSfLFseVd_Y9RwXNT,Second Level,3Kv40YSfLFseVd_Y9RwXII,Attic Level
    SRC = ifc_parent_id
    VAL_ATTR = levelName
    -> AttributeValueMapper_3
AttributeValueMapper_3
    DEFAULT_VALUE = -
    DIRECTION = Forward (Source To Destination)
    LUT = 3Kv40YSfLFseVd_Y9RwXhc,-2.6,3Kv40YSfLFseVd_Y9RwJu1,0.2,3Kv40YSfLFseVd_Y9RwJCd,3.1,3Kv40YSfLFseVd_Y9RwXNT,6.0,3Kv40YSfLFseVd_Y9RwXII,8.9
    SRC = ifc_parent_id
    VAL_ATTR = elevationRelative
    -> AttributeKeeper
AttributeKeeper
    CREATE_BULK_MODE_FEATURES = No
    KEEP_ATTRS = GlobalId,LongName,Name,ObjectType,cesEntityType,cesLegalSpaceSubtype,cesLegalSpaceType,cesPhysicalProperty,elevationRelative,fme_feature_type,ifc_parent_id,ifc_parent_unique_id,ifc_type_object_id,ifc_unique_id,levelName,ifc_instance_name,PredefinedType
    KEEP_LIST = ifc_property_set{} ifc_quantity_set{}
    -> site
site: FeatureTypeFilter
    ATTRIBUTES = IfcBuildingStorey,<Blank>,<Unfiltered>,IfcWall,IfcSpace,IfcRoof,IfcSlab,IfcColumn,IfcDoor,IfcMember,IfcRailing,IfcStair,IfcStairFlight,IfcWindow,IfcRampFlight,IfcBuildingElementProxy,IfcOpeningElement,IfcBeam,IfcSite,IfcBuilding
    IfcWall -> AttributeExposer_5
    IfcSpace -> AttributeExposer_7
    IfcRoof -> FeatureMerger_12 [REQUESTOR]
    IfcSlab -> GeometryPartExtractor_3
    IfcColumn -> GeometryFilter_10
    IfcDoor -> FeatureMerger_9 [REQUESTOR]
    IfcMember -> FeatureMerger_11 [REQUESTOR]
    IfcRailing -> FeatureMerger_11 [REQUESTOR]
    IfcStair -> AttributeCreator_4
    IfcStairFlight -> FeatureMerger_11 [REQUESTOR]
    IfcWindow -> FeatureMerger_9 [REQUESTOR]
    IfcRampFlight -> GeometryFilter_6
    IfcOpeningElement -> GeometryPartExtractor_5
    IfcOpeningElement -> FeatureMerger_10 [REQUESTOR]
    IfcBeam -> GeometryFilter_10
    IfcSite -> GeometryFilter_6
    IfcBuilding -> Aggregator_9

Bookmark: Spaces
AttributeFilter_2
    ATTR_NAME = LongName
    ATTR_VALUES = <Empty>,<Missing>,<Null>,<Unfiltered>,Space,Room
    Space -> FeatureMerger_13 [REQUESTOR]
FeatureMerger
    ATTR_ACCUM_MODE = Merge Supplier
    ATTR_CONFLICT_RES = Use Requestor
    IGNORE_NULLS = No
    JOIN_KEYS = @Value(Name) @Value(Number) AUTO
    MERGE_TYPE = Attributes Only
    PROCESS_DUPS = NO
    REJECT_NULL_MISSING_KEYS = No
    SUPPLIERS_FIRST = No
    MERGED -> AttributeManager_17
AttributeManager_17
    ATTR_TABLE = RENAME_SET_VALUE Area > AreaSpaceSch (varchar(200))
    USER_EXPOSED_ATTRIBUTES = ifc_instance_name
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(Zone) CONTAINS CU",@Value(Name) CONTAINS CU
    @Value(Name) CONTAINS CU -> AttributeManager_22
    <UNFILTERED> -> AttributeManager_13
AttributeManager_22
    ATTR_TABLE:
      SET_TO cesLegalSpaceType = Condominium Units
      SET_TO cesLegalSpaceSubtype = Condominium Unit
      SET_TO cesPhysicalProperty = -
      SET_TO Name = @Value(Zone)
    -> FeatureMerger_2 [SUPPLIER]
    -> GeometryFilter
AttributeManager_13
    ATTR_TABLE:
      SET_TO cesLegalSpaceType = Common Places
      SET_TO cesLegalSpaceSubtype = Common Place
      SET_TO cesPhysicalProperty = -
      SET_TO Name = @Value(Zone)
    -> FeatureMerger_5 [SUPPLIER]
    -> GeometryFilter
GeometryFilter
    BREAK_AGG = No
    GEOM_PORT_NAMES = Point Line Arc Area Ellipse Text Raster "Point Cloud" Surface Solid Collection Null Instance
    SURFACE -> Deaggregator_2
    SOLID -> AttributeManager_8
Deaggregator_2
    COPY_ATTR = Every Node
    EXPLODE_INSTANCES = No
    ID_ATTR = _hierarchy_id
    ID_SELECTION = ID and Parent ID
    LIST_ATTR_MODE_LOOKUP = LEAN
    MODE = Preserve Hierarchy
    PARENT_ID_ATTR = _hierarchy_parent_id
    SPLIT_COMPOSITES = No
    DEAGGREGATED -> GeometryFilter_4
GeometryFilter_4
    BREAK_AGG = No
    GEOM_PORT_NAMES = Surface
    SURFACE -> GeometryCoercer_3
GeometryCoercer_3
    GQUERY:
      for $geom in //geometry
      where $geom/count(parent::geometry) = 0
      return number($geom/@fme_id)
    KIND = fme_brep_solid
    COERCED -> AttributeManager_8
AttributeManager_8
    ATTR_TABLE:
      SET_TO cesPhysicalProperty = Space
      SET_TO Area = @round(@Value(Area),2)
      SET_TO Volume = @round(@Value(Volume),2)
      SET_TO Sorter = 999
      RENAME_SET_VALUE GrossFloorArea > GrossFloorAreaSpace = @round(@Value(GrossFloorAreaSpace),2)
      RENAME_SET_VALUE GrossFootprintArea > GrossFootprintAreaSpace
      RENAME_SET_VALUE Height > HeightSpace
      RENAME_SET_VALUE NetVolume > NetVolumeSpace = @round(@Value(NetVolumeSpace),2)
      RENAME_SET_VALUE NetFloorArea > NetFloorAreaSpace = @round(@Value(NetFloorAreaSpace),2)
    -> Reprojector_5
    -> AttributeFilter_3

Bookmark: Legal Spaces
AttributeFilter_3
    ATTR_NAME = cesLegalSpaceSubtype
    ATTR_VALUES = <Empty>,<Missing>,<Null>,<Unfiltered>,Condominium Unit,Common Place
    Condominium Unit -> Sorter
    Common Place -> Sorter_2
Aggregator_4
    ACCUM_ATTRS_NAME = Merge Incoming Attributes
    AGGREGATE_TYPE = Homogeneous Collection (If Possible)
    GROUP_BY = GlobalId_IfcWall
    MODE = Geometry - Assemble One Level
    SEP = ,
    AGGREGATE -> AttributeManager_24
AttributeManager_24
    ATTR_TABLE:
      RENAME_SET_VALUE GrossVolume > WallGrossVolume
      RENAME_SET_VALUE NetVolume > WallNetVolume
    -> AttributeFilter
DuplicateFilter_3 [off]
    INPUT_ORDERED_CHOICE = No
    KEYATTR = GlobalId_IfcWall
    UNIQUE -> AttributeFilter
AttributeFilter
    ATTR_NAME = cesLegalSpaceSubtype
    ATTR_VALUES = <Empty>,<Missing>,<Null>,<Unfiltered>,Walls inside legal condominium space,Exterior and/or Load Bearing Walls,Walls in common places,Walls between condominium units
    Walls inside legal condominium space -> Sorter
    Exterior and/or Load Bearing Walls -> Aggregator_5
    Walls in common places -> Aggregator_5
    Walls between condominium units -> Aggregator_5
Sorter
    SORT_PARM = Sorter NATURAL DESCENDING
    SORTED -> Aggregator_2
Aggregator_2
    ACCUM_ATTRS_NAME = Merge Incoming Attributes
    AGGREGATE_TYPE = Homogeneous Collection (If Possible)
    GROUP_BY = Zone
    MODE = Geometry - Assemble One Level
    SEP = ,
    SUM = Area Volume CrossSectionArea GrossArea GrossFloorArea GrossFootprintArea GrossVolume NetVolume _volume wallAreaFootprint
    AGGREGATE -> AppearanceRemover
footprintAra_2
    AreaCalculator_2_Output -> VolumeCalculator_5
VolumeCalculator_5
    MULT = 1
    SET_TRAIT = No
    VOLUME_ATTR = VolumeSpace
    -> AttributeRounder
AttributeRounder
    PLACES = 2
    ROUND_TYPE = Nearest
    SRC_ATTRS = Area Volume footprintArea_CAL NetVolumeSpace VolumeSpace
    -> AttributeValueMapper_2
AttributeValueMapper_2
    DIRECTION = Forward (Source To Destination)
    LUT = CU_1,46/318,CU_2,48/318,CU_3,50/318,CU_4,50/318,CU_5,62/318,CU_6,62/318
    SRC = Zone
    VAL_ATTR = share
    -> Reprojector_7
Note: Common spaces
Aggregator_5
    ACCUM_ATTRS_NAME = Merge Incoming Attributes
    AGGREGATE_TYPE = Homogeneous Collection (If Possible)
    GROUP_BY = ifc_parent_id
    MODE = Geometry - Assemble One Level
    SEP = ,
    SUM = Area Volume CrossSectionArea GrossArea GrossFloorArea GrossFootprintArea area wallAreaFootprint GrossVolume _volume WallNetVolume WallGrossVolume
    AGGREGATE -> Sorter_2
Sorter_2
    SORT_PARM = Sorter NATURAL DESCENDING
    SORTED -> Aggregator_3
Note: Common spaces
Aggregator_3
    ACCUM_ATTRS_NAME = Merge Incoming Attributes
    AGGREGATE_TYPE = Homogeneous Collection (If Possible)
    GROUP_BY = ifc_parent_id
    MODE = Geometry - Assemble One Level
    SEP = ,
    SUM = NetVolume WallGrossVolume
    AGGREGATE -> AppearanceRemover_2
AppearanceRemover_2
    SIDE_TO_REMOVE = Front and Back Sides
    -> VolumeCalculator_2
VolumeCalculator_2
    MULT = 1
    SET_TRAIT = No
    VOLUME_ATTR = Volume
    -> footprintAra [SurfaceFootprintReplacer_2_Input]
footprintAra
    AreaCalculator_2_Output -> AttributeRounder_2

Bookmark: Columns
VolumeCalculator
    MULT = 1
    SET_TRAIT = No
    VOLUME_ATTR = Volume
    -> AttributeManager_12
AttributeManager_12
    ATTR_TABLE:
      SET_TO cesLegalSpaceType = Common Places
      SET_TO cesPhysicalProperty = Frame
      SET_TO Volume = @round(@Value(Volume),2)
    -> Aggregator_5
    -> AttributeValueMapper_4

Bookmark: Slabs
GeometryPartExtractor_3
    GQUERY:
      for $geom in //geometry
      where $geom/@fme_geometry_type = ('IFMEBox', 'IFMEBRepSolid', 'IFMEExtrusion', 'IFMEMultiSolid', 'IFMECompositeSolid', 'IFMECSGSolid')
      return number($geom/@fme_id)
    EXTRACTED -> AttributeFilter_4
    UNTOUCHED -> SolidBuilder
SolidBuilder
    ACCUM_ATTRS_NAME = Use Attributes From One Feature
    DROP_HOLES = No
    HOLE_ATTR = _is_void
    SOLID -> AttributeManager_11
AttributeFilter_4
    ATTR_NAME = PredefinedType
    ATTR_VALUES = <Unfiltered>,<Empty>,<Missing>,<Null>,ROOF
    <UNFILTERED> -> AttributeManager_11
    ROOF -> FeatureMerger_12 [SUPPLIER]
AttributeManager_11
    ATTR_TABLE:
      SET_TO cesLegalSpaceType = Common Places
      SET_TO area = @Area()
    -> Aggregator_5
    -> Reprojector_4

Bookmark: Roof
FeatureMerger_12
    ATTR_ACCUM_MODE = Merge Supplier
    ATTR_CONFLICT_RES = Use Requestor
    GEOM_TYPE = Build Aggregates
    IGNORE_NULLS = No
    JOIN_KEYS = @Value(ifc_unique_id) @Value(ifc_parent_unique_id) STRING
    MERGE_TYPE = Attributes and Geometry
    PROCESS_DUPS = YES
    REJECT_NULL_MISSING_KEYS = No
    SUPPLIERS_FIRST = Yes
    MERGED -> BoundsExtractor
BoundsExtractor
    XMAX = _xmax
    XMIN = _xmin
    YMAX = _ymax
    YMIN = _ymin
    ZMAX = _zmax
    ZMIN = _zmin
    -> AttributeManager_10
AttributeManager_10
    ATTR_TABLE:
      SET_TO cesEntityType = IfcRoof
      SET_TO cesLegalSpaceType = Common Places
      SET_TO cesLegalSpaceSubtype = Roof
      SET_TO cesPhysicalProperty = Roof
      SET_TO topElevation = @round(@Value(_zmax),2)
    -> Reprojector_2
    -> Aggregator_5

Bookmark: wall
AreaCalculator_2
    AREA_ATTR = _area
    AREA_TYPE = Sloped Area
    MULT = 1
SurfaceFootprintReplacer
    OFFSET_Z = Minimum Z
    SHADOW_MODE = Overhead Shadow
    FOOTPRINT -> AreaCalculator
AreaCalculator
    AREA_ATTR = wallAreaFootprint
    AREA_TYPE = Plane Area
    MULT = 1
    -> FeatureMerger_15 [SUPPLIER]
FeatureMerger_15
    ATTR_ACCUM_MODE = Merge Supplier
    ATTR_CONFLICT_RES = Use Requestor
    IGNORE_NULLS = No
    JOIN_KEYS = @Value(GlobalId_IfcWall) @Value(GlobalId_IfcWall) AUTO
    MERGE_TYPE = Attributes Only
    PROCESS_DUPS = NO
    REJECT_NULL_MISSING_KEYS = No
    SUPPLIERS_FIRST = No
    MERGED -> GeometryFilter_3
GeometryFilter_3
    FILTER_MODE = SIMPLE
    FILTER_MULTI = FILTER_TYPES]"Null Point Text Line Area Surface Solid Raster PointCloud VoxelGrid"]FME_CONTROLLER_QUERY_FILE]]FME_CONTROLLER_CHOICE]Simple
    Surface -> GeometryCoercer_4
    Solid -> Junction_6
GeometryCoercer_4
    GQUERY:
      for $geom in //geometry
      where $geom/count(parent::geometry) = 0
      return number($geom/@fme_id)
    KIND = fme_brep_solid
    COERCED -> Junction_6
Note: All walls
Junction_6
    -> DuplicateFilter_5
DuplicateFilter_5
    INPUT_ORDERED_CHOICE = No
    KEYATTR = GlobalId_IfcWall
    UNIQUE -> AttributeFilter_5

Bookmark: Walls by legal type
AttributeFilter_7
    ATTR_NAME = LoadBearing
    ATTR_VALUES = Yes,No,<Missing>,<Null>,<Unfiltered>,<Empty>
    Yes -> AttributeManager
    No -> AttributeManager_3
AttributeManager_3
    ATTR_TABLE = SET_TO cesPhysicalProperty = Interior
    -> AttributeExposer_2
AttributeExposer_2
    ATTR_LIST = ifc_instance_name
    -> AttributeRenamer
AttributeRenamer
    ATTR_TABLE = RENAME_SET_DEFAULT ifc_instance_name > wall_ifc_instance_name
    -> FeatureMerger_3 [SUPPLIER]
Note: Exterior and/or load bearing walls
AttributeManager
    ATTR_TABLE:
      SET_TO cesLegalSpaceType = Common Places
      SET_TO cesLegalSpaceSubtype = Exterior and/or Load Bearing Walls
      SET_TO cesPhysicalProperty = Exterior
      SET_TO GlobalId = @Value(GlobalId_IfcWall)
    -> Junction_5
FeatureMerger_3
    ATTR_ACCUM_MODE = Merge Supplier
    ATTR_CONFLICT_RES = Use Requestor
    IGNORE_NULLS = No
    JOIN_KEYS = @Value(RelatedBuildingElement) @Value(wall_ifc_instance_name) AUTO
    MERGE_TYPE = Attributes and Geometry
    PROCESS_DUPS = NO
    REJECT_NULL_MISSING_KEYS = No
    SUPPLIERS_FIRST = No
    MERGED -> FeatureMerger_5 [REQUESTOR]
Note: walls inside or outline of common places
FeatureMerger_5
    ATTR_ACCUM_MODE = Merge Supplier
    ATTR_CONFLICT_RES = Use Requestor
    IGNORE_NULLS = No
    JOIN_KEYS = @Value(RelatingSpace) @Value(ifc_instance_name) AUTO
    MERGE_TYPE = Attributes Only
    PROCESS_DUPS = NO
    REJECT_NULL_MISSING_KEYS = No
    SUPPLIERS_FIRST = No
    MERGED -> AttributeManager_5
    UNMERGED_REQUESTOR -> FeatureMerger_6 [REQUESTOR]
AttributeManager_5
    ATTR_TABLE:
      SET_TO cesLegalSpaceType = Common Places
      SET_TO cesLegalSpaceSubtype = Walls in common places
    -> DuplicateFilter_4
    -> FeatureMerger_6 [SUPPLIER]
DuplicateFilter_4
    INPUT_ORDERED_CHOICE = No
    KEYATTR = GlobalId_IfcWall
    UNIQUE -> Junction_5
Note: walls inside cu or cu seperators
FeatureMerger_6
    ATTR_ACCUM_MODE = Merge Supplier
    ATTR_CONFLICT_RES = Use Requestor
    IGNORE_NULLS = No
    JOIN_KEYS = @Value(wall_ifc_instance_name) @Value(wall_ifc_instance_name) AUTO
    MERGE_TYPE = Attributes Only
    PROCESS_DUPS = NO
    REJECT_NULL_MISSING_KEYS = No
    SUPPLIERS_FIRST = No
    UNMERGED_REQUESTOR -> FeatureMerger_2 [REQUESTOR]
FeatureMerger_2
    ATTR_ACCUM_MODE = Merge Supplier
    ATTR_CONFLICT_RES = Use Requestor
    IGNORE_NULLS = No
    JOIN_KEYS = @Value(RelatingSpace) @Value(ifc_instance_name) AUTO
    MERGE_TYPE = Attributes Only
    PROCESS_DUPS = NO
    REJECT_NULL_MISSING_KEYS = No
    SUPPLIERS_FIRST = No
    MERGED -> DuplicateFilter
DuplicateFilter
    INPUT_ORDERED_CHOICE = No
    KEYATTR = Zone wall_ifc_instance_name
    UNIQUE -> DuplicateFilter_2
Note: cu seperation
DuplicateFilter_2
    INPUT_ORDERED_CHOICE = No
    KEYATTR = wall_ifc_instance_name
    UNIQUE -> FeatureMerger_7 [REQUESTOR]
    DUPLICATE -> AttributeManager_6
    DUPLICATE -> FeatureMerger_7 [SUPPLIER]
FeatureMerger_7
    ATTR_ACCUM_MODE = Merge Supplier
    ATTR_CONFLICT_RES = Use Requestor
    IGNORE_NULLS = No
    JOIN_KEYS = @Value(wall_ifc_instance_name) @Value(wall_ifc_instance_name) AUTO
    MERGE_TYPE = Attributes Only
    PROCESS_DUPS = NO
    REJECT_NULL_MISSING_KEYS = No
    SUPPLIERS_FIRST = No
    UNMERGED_REQUESTOR -> AttributeManager_7
Note: in cu space
AttributeManager_7
    ATTR_TABLE:
      SET_TO GlobalId = @Value(GlobalId_IfcWall)
      SET_TO cesLegalSpaceType = Condominium Space
      SET_TO cesLegalSpaceSubtype = Walls inside legal condominium space
    -> Junction_5
AttributeManager_6
    ATTR_TABLE:
      SET_TO cesLegalSpaceType = Common Places
      SET_TO cesLegalSpaceSubtype = Walls between condominium units
      SET_TO GlobalId = @Value(GlobalId_IfcWall)
    -> Junction_5

Bookmark: Accessories
FeatureMerger_10
    ATTR_ACCUM_MODE = Merge Supplier
    ATTR_CONFLICT_RES = Use Requestor
    IGNORE_NULLS = No
    JOIN_KEYS = @Value(ifc_parent_id) @Value(GlobalId_IfcWall) AUTO
    MERGE_TYPE = Attributes Only
    PROCESS_DUPS = NO
    REJECT_NULL_MISSING_KEYS = No
    SUPPLIERS_FIRST = No
    MERGED -> FeatureMerger_9 [SUPPLIER]
FeatureMerger_9
    ATTR_ACCUM_MODE = Merge Supplier
    ATTR_CONFLICT_RES = Use Requestor
    IGNORE_NULLS = No
    JOIN_KEYS = @Value(ifc_parent_id) @Value(GlobalId) AUTO
    MERGE_TYPE = Attributes Only
    PROCESS_DUPS = NO
    REJECT_NULL_MISSING_KEYS = No
    SUPPLIERS_FIRST = No
    MERGED -> AttributeManager_14
AttributeManager_14
    ATTR_TABLE:
      SET_TO cesPhysicalProperty = Accessories
      SET_TO ifc_parent_id = @Value(ifc_parent_id_IfcWall)
    -> Deaggregator_7
Deaggregator_7
    EXPLODE_INSTANCES = Yes
    GEOM_NAME_FIELD = _geometry_name
    LIST_ATTR_MODE_LOOKUP = LEAN
    MODE = Flatten All Levels
    SPLIT_COMPOSITES = Yes
    DEAGGREGATED -> GeometryFilter_9
GeometryFilter_9
    BREAK_AGG = No
    GEOM_PORT_NAMES = Solid
    SOLID -> Aggregator_7
Aggregator_7
    ACCUM_ATTRS_NAME = Use Attributes From One Feature
    AGGREGATE_TYPE = Homogeneous Collection (If Possible)
    GROUP_BY = GlobalId
    MODE = Geometry - Assemble One Level
    SEP = ,
    AGGREGATE -> Junction_8
AttributeCreator_4
    ATTR_TABLE = SET_TO storey_id = @Value(ifc_parent_id)
    -> FeatureMerger_11 [SUPPLIER]
FeatureMerger_11
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(ifc_parent_id) @Value(GlobalId) AUTO
    MERGE_TYPE = Attributes Only
    PROCESS_DUPS = YES
    REJECT_NULL_MISSING_KEYS = No
    SUPPLIERS_FIRST = No
    MERGED -> AttributeManager_15
    UNMERGED_REQUESTOR -> GeometryPartExtractor_4
    USED_SUPPLIER -> GeometryPartExtractor_4
AttributeManager_15
    ATTR_TABLE = SET_TO ifc_parent_id = @Value(storey_id)
    -> GeometryPartExtractor_4
GeometryPartExtractor_4
    GQUERY:
      for $geom in //geometry
      where $geom/@fme_geometry_type = ('IFMEBox', 'IFMEBRepSolid', 'IFMEExtrusion', 'IFMEMultiSolid', 'IFMECompositeSolid', 'IFMECSGSolid')
      return number($geom/@fme_id)
    EXTRACTED -> Aggregator_8
    UNTOUCHED -> Deaggregator_6
Aggregator_8
    ACCUM_ATTRS_NAME = Use Attributes From One Feature
    AGGREGATE_TYPE = Homogeneous Collection (If Possible)
    GROUP_BY = GlobalId
    MODE = Geometry - Assemble One Level
    SEP = ,
    AGGREGATE -> Junction_8
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter_8
GeometryFilter_8
    BREAK_AGG = No
    GEOM_PORT_NAMES = Surface Point Line Arc Area Ellipse Text Raster "Point Cloud" Solid Collection Null Instance
    SURFACE -> Aggregator_6
Aggregator_6
    ACCUM_ATTRS_NAME = Use Attributes From One Feature
    AGGREGATE_TYPE = Homogeneous Collection (If Possible)
    GROUP_BY = fme_feature_type GlobalId
    MODE = Geometry - Assemble One Level
    SEP = ,
    AGGREGATE -> GeometryCoercer_5
GeometryCoercer_5
    GQUERY:
      for $geom in //geometry
      where $geom/count(parent::geometry) = 0
      return number($geom/@fme_id)
    KIND = fme_brep_solid
    COERCED -> Junction_8
Junction_8
    -> AttributeManager_16
AttributeManager_16
    ATTR_TABLE = SET_TO cesPhysicalProperty = Accessories
    -> AttributeValueMapper_5

Bookmark: External Area
GeometryFilter_6
    BREAK_AGG = No
    GEOM_PORT_NAMES = Point Line Arc Area Ellipse Text Raster "Point Cloud" Surface Solid Collection Null Instance
    SURFACE -> Deaggregator_3
    COLLECTION -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter_7
GeometryFilter_7
    BREAK_AGG = No
    GEOM_PORT_NAMES = Point Line Arc Area Ellipse Text Raster "Point Cloud" Surface Solid Collection Null Instance
    SURFACE -> GeometryCoercer_2
AttributeManager_18
    ATTR_TABLE:
      SET_TO cesLegalSpaceType = Common Places
      SET_TO cesLegalSpaceSubtype = Setback area
      SET_TO cesPhysicalProperty = External Area
      SET_TO area = @round(@Area(),2)
    -> AppearanceRemover_3

Bookmark: New Bookmark
Parcel (reader DGNV8_1)
    -> AttributeExposer_4
BuildingFootprint (reader DGNV8_1)
    -> AttributeExposer_4
AttributeExposer_4
    ATTR_LIST = fme_feature_type
    -> AttributeCreator_2
AttributeCreator_2
    ATTR_TABLE:
      SET_TO cesEntityType = @Value(fme_feature_type)
      SET_TO cesLegalSpaceType
      SET_TO cesLegalSpaceSubtype
      SET_TO cesPhysicalProperty
    -> FeatureTypeFilter
FeatureTypeFilter
    ATTRIBUTES = <Blank>,<Unfiltered>,BuildingFootprint,Parcel
    BuildingFootprint -> FaceReplacer_2
    Parcel -> AttributeManager_2
AttributeManager_2
    ATTR_TABLE:
      SET_TO cesLegalSpaceType = Common surface
      SET_TO cesLegalSpaceSubtype = Surface parcel
      SET_TO propertyID = 1556722
      SET_TO parcelNumber = 46
      SET_TO lotNumber = 5813
      SET_TO sheetNumber = 342-345
      SET_TO district = Gazi
      SET_TO city = Ankara
      SET_TO area = @round(@Area(),2)
      SET_TO useType = Residental
    -> FaceReplacer
    -> Bufferer
Bufferer
    ANGLE = 22.5
    CAP_STYLE = Arc
    CORNER_STYLE = Arc
    MODE = AREA
    OFFSET = 0.01
    OFFSET_UNITS = NONE
    PRECISION = APPROX
    BUFFERED -> Offsetter
Offsetter
    MODE = Cartesian Coordinate
    XOFF = 0
    YOFF = 0
    ZOFF = -2.75
    OFFSET -> Extruder
Extruder
    DIRECTION = Auto
    DISTANCE = 16.11
    EXTRUDED -> VolumeCalculator_3
VolumeCalculator_3
    MULT = 1
    SET_TRAIT = No
    VOLUME_ATTR = Volume
    -> AttributeManager_20
AttributeManager_20
    ATTR_TABLE:
      SET_TO cesLegalSpaceType = Common Places
      SET_TO cesLegalSpaceSubtype = 3D parcel
      SET_TO Volume = @round(@Value(Volume),2)
    -> Reprojector_13
FaceReplacer
    ANGULAR_TOLERANCE_CHOICE = Automatic
    THICKNESS_TOLERANCE_CHOICE = Ignore
    -> Reprojector_3
FaceReplacer_2
    ANGULAR_TOLERANCE_CHOICE = Automatic
    THICKNESS_TOLERANCE_CHOICE = Ignore
    -> AttributeManager_4
AttributeManager_4
    ATTR_TABLE:
      SET_TO cesLegalSpaceType = Common surface
      SET_TO cesLegalSpaceSubtype = Building footprint
      SET_TO propertyID = 1556722
      SET_TO parcelNumber = 46
      SET_TO lotNumber = 5816
      SET_TO sheetNumber = 342-345
      SET_TO district = Gazi
      SET_TO city = Ankara
      SET_TO area = @round(@Area(),2)
    -> Reprojector_11

FME custom transformer footprintAra

SurfaceFootprintReplacer_2_Input (input)
    -> SurfaceFootprintReplacer_2
    -> FeatureMerger [REQUESTOR]
SurfaceFootprintReplacer_2
    OFFSET_Z = Minimum Z
    SHADOW_MODE = Overhead Shadow
    FOOTPRINT -> AreaCalculator_2
AreaCalculator_2
    AREA_ATTR = footprintArea_CAL
    AREA_TYPE = Plane Area
    MULT = 1
    -> FeatureMerger [SUPPLIER]
FeatureMerger
    ATTR_ACCUM_MODE = Merge Supplier
    ATTR_CONFLICT_RES = Use Requestor
    IGNORE_NULLS = No
    JOIN_KEYS = GlobalId GlobalId AUTO
    MERGE_TYPE = Attributes Only
    PROCESS_DUPS = NO
    REJECT_NULL_MISSING_KEYS = No
    SUPPLIERS_FIRST = No
    MERGED -> AreaCalculator_2_Output (output)
AreaCalculator_2_Output (output)
